package security_controls {
private import ScalarFunctions::*;
  //import security::definitions::*;

  item def SecurityPolicy;
  item def SecurityControl;

  //trace SecurityControl -> SecurityPolicy;
}
