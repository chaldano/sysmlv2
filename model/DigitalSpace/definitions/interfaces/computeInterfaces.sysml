package ComputeInterfaces {
    private import foundations_identity::*;
    private import foundations_datetype::*;
  
    private import ScalarValues::*;
    
 abstract interface def HTTPinterface;
 abstract interface def SMBinterface;
 abstract interface def WebDavinterface;


}
