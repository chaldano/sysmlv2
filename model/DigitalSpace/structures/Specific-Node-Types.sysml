package Compute_Nature {
  private import ScalarValues::*; 
  private import 'foundations_identity'::*;
  item def NodeNature; 
  item def PhysicalNode specializes NodeNature; 
  item def VirtualNode specializes NodeNature;
}
