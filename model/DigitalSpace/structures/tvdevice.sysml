package mobileDevices {

    //private import computeNodes::*;
    private import mobilNodes::*;
    private import structuralUnits::*;

    part bNode:AppleNode{
        mobilOS = OSFamily::IOS;
        mobilCPU=CPUFamily::A_Serie;
    }


}
